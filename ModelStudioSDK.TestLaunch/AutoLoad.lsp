(command "netload" "C:\\Users\\User\\AppData\\Roaming\\Nanosoft\\nanoCAD x64 22.0\\Addins\\Pir.Mechanics.dll")
(command "netload" "C:\\Users\\User\\AppData\\Roaming\\Nanosoft\\nanoCAD x64 22.0\\Addins\\ModelStudioSDK\\ModelStudioSDK.TestsLaunch.dll")
(command "RunCADtests")
(command "Exit")
